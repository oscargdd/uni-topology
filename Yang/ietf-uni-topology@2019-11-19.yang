module ietf-uni-topology {
  yang-version 1.1;
  namespace "urn:ietf:params:xml:ns:yang:ietf-uni-topology";
  prefix uni;

  import ietf-interfaces {
    prefix if;
    reference
    "RFC 8343: A YANG Data Model for Interface Management";

  }
  import ietf-network-topology {
    prefix nt;
    reference
       "Section 6.2 of RFC 8345: A YANG Data Model for Network Topologies";

  }
  import ietf-network {
    prefix nw;
    reference
       "Section 6.1 of RFC 8345: A YANG Data Model for Network Topologies";

  }

  organization
   "IETF OPSA (Operations and Management Area) Working Group ";
 contact
   "   Editor:    Oscar Gonzalez de Dios
                 <mailto:oscar.gonzalezdedios@telefonica.com>
       Editor:   Samier Barguil
                 <mailto:alejandro.aguado_martin@nokia.com>
       Editor:    Qin Wu
                 <mailto:victor.lopezalvarez@telefonica.com>
       Editor:   Mohamed Boucadair
                 <mailto:daniel.voyer@bell.ca>
   ";
    description
   "This YANG module defines a model for representing, managing
   and controlling the User Network Interface (UNI) topology.
   Copyright (c) 2019 IETF Trust and the persons identified as
   authors of the code.  All rights reserved.

   Redistribution and use in source and binary forms, with or
   without modification, is permitted pursuant to, and subject to
   the license terms contained in, the Simplified BSD License set
   forth in Section 4.c of the IETF Trust's Legal Provisions
   Relating to IETF Documents
   (https://trustee.ietf.org/license-info).

   This version of this YANG module is part of RFC XXXX
   (https://www.rfc-editor.org/info/rfcXXXX); see the RFC itself
   for full legal notices.

   The key words 'MUST', 'MUST NOT', 'REQUIRED', 'SHALL', 'SHALL
   NOT', 'SHOULD', 'SHOULD NOT', 'RECOMMENDED', 'NOT RECOMMENDED',
   'MAY', and 'OPTIONAL' in this document are to be interpreted as
   described in BCP 14 (RFC 2119) (RFC 8174) when, and only when,
   they appear in all capitals, as shown here.";

 revision 2019-12-10 {
    description
    "Initial version";
    reference
      "draft-ogondio-opsawg-uni-topology";
    }

  grouping uni-information-group {
    list service-attachment-point {
      key "attachment-id";
      leaf attachment-id {
        type nt:tp-id;
        description
          "Name of the Interface";
      }
      leaf type {
        type identityref {
          base if:interface-type;
        }
        config false;
        description
          "The type of the interface.
           When an interface entry is created, a server MAY
           initialize the type leaf with a valid value, e.g., if it
           is possible to derive the type from the name of the
           interface.
           If a client tries to set the type of an interface to a
           value that can never be used by the system, e.g., if the
           type is not supported or if the type does not match the
           name of the interface, the server MUST reject the request.
           A NETCONF server MUST reply with an rpc-error with the
           error-tag 'invalid-value' in this case.";
        reference
          "RFC 2863: The Interfaces Group MIB - ifType";
      }
      leaf admin-status {
        type boolean;
        description
          "Administrative Status UP/DOWN";
      }
      leaf oper-status {
         type boolean;
        description
          "Operational Status UP/DOWN";
      }
      leaf encapsulation-type {
        type string;
        description
          "Encapsulation type.  By default, the
           encapsulation type is set to 'untagged'.";
      }
      description
        "service-edge-point refers to the available ports on
         the network.";
    }
    description
      "UNI Information";
  }

  augment "/nw:networks/nw:network/nw:network-types" {
       container uni-topology {
         presence "indicates UNI Unicast topology";
         description
           "The presence of the container node indicates UNI 
           topology";
       }
       description
         "Introduces new network type for UNI Unicast topology";
       }

  augment "/nw:networks/nw:network/nw:node" {
    description
      "Parameters for the service edge point level.";
    uses uni-information-group;
  }
}
